module vyatta-system-time-routing-instance-v1 {
	namespace "urn:vyatta.com:mgmt:vyatta-system-time-routing-instance:1";
	prefix vyatta-system-time-routing-instance-v1;

	import vyatta-system-v1 {
		prefix system;
	}
	import vyatta-system-time-v1 {
		prefix time;
	}
	import vyatta-routing-v1 {
		prefix rt-instance;
	}
	import configd-v1 {
		prefix configd;
	}
	organization "AT&T Inc.";
	contact
		"AT&T
		 Postal: 208 S. Akard Street
				 Dallas, TX 75202
		 Web: www.att.com";

	description
		"Copyright (c) 2017-2019, AT&T Intellectual Property.
		All rights reserved.

		Copyright (c) 2016-2017 by Brocade Communications Systems, Inc.
		All rights reserved.

		Redistribution and use in source and binary forms, with or without
		modification, are permitted provided that the following conditions
		are met:

		  1. Redistributions of source code must retain the above copyright
		     notice, this list of conditions and the following disclaimer.
		  2. Redistributions in binary form must reproduce the above
		     copyright notice, this list of conditions and the following
		     disclaimer in the documentation and/or other materials provided
		     with the distribution.
		  3. Neither the name of the copyright holder nor the names of its
		     contributors may be used to endorse or promote products derived
		     from this software without specific prior written permission.

		THIS SOFTWARE IS PROVIDED BY THE COPYRIGHT HOLDERS AND CONTRIBUTORS
		'AS IS' AND ANY EXPRESS OR IMPLIED WARRANTIES, INCLUDING, BUT NOT
		LIMITED TO, THE IMPLIED WARRANTIES OF MERCHANTABILITY AND FITNESS
		FOR A PARTICULAR PURPOSE ARE DISCLAIMED. IN NO EVENT SHALL THE
		COPYRIGHT HOLDER OR CONTRIBUTORS BE LIABLE FOR ANY DIRECT, INDIRECT,
		INCIDENTAL, SPECIAL, EXEMPLARY, OR CONSEQUENTIAL DAMAGES (INCLUDING,
		BUT NOT LIMITED TO, PROCUREMENT OF SUBSTITUTE GOODS OR SERVICES;
		LOSS OF USE, DATA, OR PROFITS; OR BUSINESS INTERRUPTION) HOWEVER
		CAUSED AND ON ANY THEORY OF LIABILITY, WHETHER IN CONTRACT, STRICT
		LIABILITY, OR TORT (INCLUDING NEGLIGENCE OR OTHERWISE) ARISING IN
		ANY WAY OUT OF THE USE OF THIS SOFTWARE, EVEN IF ADVISED OF THE
		POSSIBILITY OF SUCH DAMAGE.

		SPDX-License-Identifier: BSD-3-Clause

		VRF NTP configuration";

	revision 2017-01-31 {
		description "Rework YANG nodeset != comparisons.";
	}

	revision 2016-06-16 {
		description "Initial revision of version 1.";
	}

	augment /rt-instance:routing/rt-instance:routing-instance/rt-instance:system {
		uses time:system-time-ntp {
			refine ntp {
				configd:create "/opt/vyatta/sbin/vyatta_configure_ntp.pl --operation=start --rtinstance=$VAR(../../@)";
				configd:delete "/opt/vyatta/sbin/vyatta_configure_ntp.pl --operation=stop --rtinstance=$VAR(../../@)";
				configd:update "/opt/vyatta/sbin/vyatta_configure_ntp.pl --operation=restart --rtinstance=$VAR(../../@)";
				must "count(/system:system/time:ntp/time:server) = 0" {
					error-message "Cannot also configure NTP in default routing-instance";
				}
				must "count(/rt-instance:routing/rt-instance:routing-instance[not(rt-instance:instance-name ="
				+ "current()/../../rt-instance:instance-name)]/rt-instance:system/ntp) = 0" {
					error-message "Cannot configure NTP in more than one routing-instance simultaneously";
				}
			}
		}
	}

}
